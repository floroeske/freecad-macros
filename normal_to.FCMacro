# Solidworks "normal to" equivalent

from pivy import coin


def pointAt(normal, up):
    z = normal
    y = up
    x = y.cross(z)
    y = z.cross(x)

    rot = App.Matrix()
    rot.A11 = x.x
    rot.A21 = x.y
    rot.A31 = x.z

    rot.A12 = y.x
    rot.A22 = y.y
    rot.A32 = y.z

    rot.A13 = z.x
    rot.A23 = z.y
    rot.A33 = z.z

    return App.Placement(rot).Rotation


selection = Gui.Selection.getSelectionEx()
obj = selection[0]
selected_face = obj.SubObjects[0]
dir = selected_face.normalAt(0, 0)

if dir.z == 1:
    rot = pointAt(dir, App.Vector(0.0, 1.0, 0.0))
elif dir.z == -1:
    rot = pointAt(dir, App.Vector(0.0, 1.0, 0.0))
else:
    rot = pointAt(dir, App.Vector(0.0, 0.0, 1.0))

cam = FreeCADGui.ActiveDocument.ActiveView.getCameraNode()
cam.orientation.setValue(rot.Q)

Gui.SendMsgToActiveView("ViewSelection")
